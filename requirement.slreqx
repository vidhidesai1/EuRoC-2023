# requirements

## #1: Stage1 (Functional)

### #6: row17 (Functional)
Stage 1 avionics subsystem shall feature a mandatory operational Eggtimer TRS Flight Computer for official altitude logging and GPS tracking.

### #7: row19 (Functional)
Stage 1 avionics subsystem shall transmit tracking telemetry beacon each X seconds.

### #8: row21 (Functional)
Stage 1 avionics subsystem transmit tracking telemetry beacon shall follow the predefined telemetry message structure (TBD)

### #17: row25 (Functional)
Stage 1 avionics subsystem shall deploy drogue parachute at TBD s

### #18: row26 (Functional)
Stage 1 avionics subsystem shall deploy main parachute at TBD s

### #19: row29 (Functional)
Stage 1 avionics subsystem shall not weight more than TBD g

### #20: row30 (Functional)
Stage 1 avionics subsystem shall not weight more than TBD g

### #21: row32 (Functional)
Stage 1 avionics subsystem shall be able to transmit it's telemetry beacons with a maximum error rate of TBD under a nominal velocity of TBD m/s.

### #22: row34 (Functional)
Stage 1 avionics subsystem installed in proximity of the piston's black powder mechanism shall widthstand the heat generated when activated.

## #2: Stage2 (Functional)

### #10: row18 (Functional)
Stage 2 avionics subsystem shall feature a mandatory operational Eggtimer TRS Flight Computer for official altitude logging and GPS tracking.

### #11: row20 (Functional)
Stage 2 avionics subsystem shall transmit tracking telemetry beacon each X seconds.

### #12: row22 (Functional)
Stage 2 avionics subsystem transmit tracking telemetry beacon shall follow the predefined telemetry message structure (TBD)

### #23: row23 (Functional)
Stage 2 avionics subsystem shall ignite the 2nd stage solid motor either under a time condition (elapsed seconds since launch) or a flag condition (TBD)

### #24: row24 (Functional)
Stage 2 avionics subsystem shall deploy the payloads at TBD s

### #25: row27 (Functional)
Stage 2 avionics subsystem shall deploy drogue parachute at TBD s

### #26: row28 (Functional)
Stage 2 avionics subsystem shall deploy main parachute at TBD s

### #27: row31 (Functional)
Stage 2 avionics subsystem shall automatically check that it's attitude is upwards and within TBD degrees of deviation from Earth's normal vector before igniting its propulsion.

### #28: row33 (Functional)
Stage 2 avionics subsystem shall be able to transmit it's telemetry beacons with a maximum error rate of TBD under a nominal velocity of TBD m/s.

## #3: Hardware-ALL (Functional)

### #14: row2 (Functional)
All avionics subsystems shall implement redundant recovery system electronics, including sensors/flight computers and "electric initiators".

### #15: row3 (Functional)
Redundant avionics systems shall have independent power supply.

### #16: row4 (Functional)
All avionics subsystems onboard batteries should be in accessible positions if cannot be externally charged.

### #29: row5 (Functional)
All avionics subsystems onboard batteries shall have at least six hours of battery life on the launch rail.

### #30: row6 (Functional)
All avionics subsystems onboard batteries should be capable of being charged using a feedthrough connector in the avionics hatch.

### #31: row7 (Functional)
All onboard batteries should feature the same nominal voltage.

### #32: row8 (Functional)
At least one redundant recovery system electronics subsystem shall implement a COTS flight computer

### #33: row9 (Functional)
The interconnection redundancy of the nominal and redundant recovery electronics and recovery systems should be implemented as illustrated in Figure 2 (DT&EG, pg 18).

### #34: row10 (Functional)
All avionics subsystem switches and connectors should be accessible from an avionics hatch (access panel) on the airframe.

### #35: row11 (Functional)
All of the TRS Flight Computers should be purchased with the capability to operate within the US "Ham" frequency range.

### #36: row12 (Functional)
Team shall be capable of (and prepared to) re-program their operating frequencies of Eggtimer/finder equipment at short notice in case launch schedule reshuffling requires it so.

### #37: row13 (Functional)
Team shall ensure that TRS Flight Computer is running a custom version of the firmware for the 70 cm Ham frequency band, having a channel selection resolution of 25 kHz.

### #38: row14 (Functional)
Team shall procure the Eggfinder TRS Flight Computer "full kit package", as it includes the LCD GPS receiver.

### #39: row15 (Functional)
All safety critical wiring shall implement a cable management solution (e.g., wire ties, wiring, harnesses, cable raceways) which will prevent tangling and excessive free movement of significant wiring/cable lengths due to expected launch loads.

### #40: row16 (Functional)
All safety critical wiring/cable connections shall be sufficiently secure as to prevent de-mating due to expected launch loads. This will be verified by a tug test, by hand.
